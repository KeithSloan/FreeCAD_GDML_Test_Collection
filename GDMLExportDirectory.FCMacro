# **************************************************************************
# *   Batch GDML Export – Safe, Robust, Production Version                 *
# ***************************************************************************

import os
import glob
import shutil
import traceback

import FreeCAD
import FreeCADGui
from PySide import QtGui, QtCore, QtWidgets


# -------------------------------------------------------------------------
# Directory selector widget
# -------------------------------------------------------------------------

class Directory(QtGui.QWidget):
    def __init__(self, label):
        super().__init__()
        layout = QtGui.QHBoxLayout(self)

        layout.addWidget(QtGui.QLabel(label))

        self.pathEdit = QtGui.QLineEdit("Path Not Set")
        self.pathEdit.setReadOnly(True)
        layout.addWidget(self.pathEdit)

        btn = QtGui.QPushButton("Select")
        btn.clicked.connect(self.selectDir)
        layout.addWidget(btn)

    def selectDir(self):
        path = QtWidgets.QFileDialog.getExistingDirectory(self, "Select Directory")
        if path:
            self.pathEdit.setText(path)

    def path(self):
        return self.pathEdit.text()


# -------------------------------------------------------------------------
# Main dialog
# -------------------------------------------------------------------------

class GDMLExportDialog(QtGui.QDialog):

    def __init__(self):
        super().__init__()
        self.initUI()

    def initUI(self):
        self.setWindowTitle("Batch GDML Export")
        self.setGeometry(600, 600, 700, 260)
        self.setWindowFlags(QtCore.Qt.WindowStaysOnTopHint)

        self.mainLayout = QtGui.QVBoxLayout(self)

        self.sourceDir = Directory("Source")
        self.targetDir = Directory("Target")
        self.failureDir = Directory("Failure")

        self.mainLayout.addWidget(self.sourceDir)
        self.mainLayout.addWidget(self.targetDir)
        self.mainLayout.addWidget(self.failureDir)

        self.exportBtn = QtGui.QPushButton("Export GDML")
        self.exportBtn.clicked.connect(self.onExport)
        self.mainLayout.addWidget(self.exportBtn)

    # ---------------------------------------------------------------------

    def clearLayout(self):
        while self.mainLayout.count():
            item = self.mainLayout.takeAt(0)
            w = item.widget()
            if w:
                w.deleteLater()

    # ---------------------------------------------------------------------

    def logFailure(self, failurePath, text):
        logFile = os.path.join(failurePath, "failure.log")
        with open(logFile, "a", encoding="utf-8") as f:
            f.write(text + "\n")

    # ---------------------------------------------------------------------

    def cleanupBackups(self, srcDir):
        for pattern in ("*.FCBak", "*.FCStd1", "*.FCStd2"):
            for bak in glob.glob(os.path.join(srcDir, pattern)):
                try:
                    os.remove(bak)
                except Exception:
                    pass

    # ---------------------------------------------------------------------

    def processFile(self, fcFile, targetPath):
        import freecad.gdml.exportGDML

        doc = FreeCAD.openDocument(fcFile)
        fileName = os.path.basename(fcFile)

        exportPath = None

        for obj in doc.RootObjects:
            if obj.TypeId == "App::Part":
                FreeCADGui.Selection.clearSelection()
                FreeCADGui.Selection.addSelection(obj)

                exportName = fileName[:-6] + f"-{obj.Label}.gdml"
                exportPath = os.path.join(targetPath, exportName)

                freecad.gdml.exportGDML.export([obj], exportPath)
                break

        return exportPath

    # ---------------------------------------------------------------------

    def onExport(self):
        src = self.sourceDir.path()
        tgt = self.targetDir.path()
        fail = self.failureDir.path()

        if not all([src, tgt, fail]):
            QtWidgets.QMessageBox.warning(
                self, "Missing Paths",
                "Please select Source, Target and Failure directories"
            )
            return

        os.makedirs(fail, exist_ok=True)

        processed = 0
        failures = 0
        warnings = 0

        QtWidgets.QApplication.processEvents()

        for fcFile in glob.glob(os.path.join(src, "*.FCStd")):
            processed += 1

            exportPath = None
            hadException = False
            tb = ""

            try:
                exportPath = self.processFile(fcFile, tgt)

            except BaseException:
                hadException = True
                tb = traceback.format_exc()

            # --------------------------------------------------
            # Decide outcome based on GDML file existence
            # --------------------------------------------------

            if exportPath and os.path.isfile(exportPath) and os.path.getsize(exportPath) > 0:
                # Success
                if hadException:
                    warnings += 1
                    self.logFailure(
                        fail,
                        f"\nWARNING (export completed): {fcFile}\n{tb}"
                    )
            else:
                # Real failure
                failures += 1

                failedName = os.path.basename(fcFile).replace(
                    ".FCStd", ".FAILED.FCStd"
                )

                try:
                    shutil.copy2(
                        fcFile,
                        os.path.join(fail, failedName)
                    )
                except Exception:
                    pass

                self.logFailure(
                    fail,
                    f"\nFAILED FILE: {fcFile}\n{tb}"
                )

            # Always close document
            try:
                if FreeCAD.ActiveDocument:
                    FreeCAD.closeDocument(FreeCAD.ActiveDocument.Name)
            except Exception:
                pass

            QtWidgets.QApplication.processEvents()

        self.cleanupBackups(src)

        # -----------------------------------------------------------------
        # Replace UI with summary
        # -----------------------------------------------------------------

        self.clearLayout()

        title = QtGui.QLabel("GDML Export Complete")
        title.setAlignment(QtCore.Qt.AlignCenter)
        title.setStyleSheet("font-size: 16pt; font-weight: bold;")

        info = QtGui.QLabel(
            f"Files processed : {processed}\n"
            f"Warnings        : {warnings}\n"
            f"Failures        : {failures}"
        )
        info.setAlignment(QtCore.Qt.AlignCenter)
        info.setStyleSheet("font-size: 12pt;")

        closeBtn = QtGui.QPushButton("Close")
        closeBtn.clicked.connect(self.close)

        self.mainLayout.addStretch()
        self.mainLayout.addWidget(title)
        self.mainLayout.addSpacing(10)
        self.mainLayout.addWidget(info)
        self.mainLayout.addSpacing(20)
        self.mainLayout.addWidget(closeBtn)
        self.mainLayout.addStretch()

        QtWidgets.QApplication.processEvents()
        self.repaint()


# -------------------------------------------------------------------------
# Run
# -------------------------------------------------------------------------

if FreeCAD.GuiUp:
    dlg = GDMLExportDialog()
    dlg.exec_()
else:
    print("FreeCAD GUI not available")
